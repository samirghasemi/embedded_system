# Requirements

## #1: Heater Turnoff (Functional)
اگر دمای یک اتاق از off +/- 0.6 بیشتر شد بخاری آن اتاق باید خاموش شود.

## #2: Heater Turn on (Functional)
اگر دمای اتاق از on +/- 0.6 کمتر شد در صورتی که بخاری درآن اتاق قرار داشته باشد ، باید روشن شود .

## #3: Room priority (Functional)
اگر بیش از دو اتاق به بخاری نیاز داشته باشند اولویت با اتاق دارای شماره کمتر است .

## #4: Number of heater in one room (Functional)
در هر اتاق نهایتا یک بخاری میتواند قرار بگیرد .

## #5: Max Temprature (Informational)
دمای اتاق ها نباید از 0.6+20 درجه سلسیوس بیشتر شود .

## #6: Min Temprature (Informational)
دمای اتاق ها نباید از 0.6 - 15 کم تر شود .

## #9: Heater Power (Informational)
در هنگام روشن شدن بخاری ها باید با 0.5+/-99% توان شروع به کار کنند .

## #10: Need Heater (Functional)
اگر در اتاقی بخاری موجود نباشد و در اتاق دیگری بخاری بوده و دمای اتاق بدون بخاری از آستانه get کمتر بوده و اختلاف دمای دو اتاق از آستانه dif بیشتر باشد در آنصورت بخاری باید به اتاق بدون بخاری منتقل شود .

## #12: TEMP CALCULATION (Informational)
محاسبات باید در 0.01 -/+ 0.2 انجام شود .
