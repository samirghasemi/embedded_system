# cruzcontrol

## Pushing gas pedal: Halting (Functional)
When the driver pushes gas pedal and cruz_control_mode is working , change cruz_control_mode to off

## Pushing brake: Halt (Functional)
When the driver pushes the break pedal , change mode cruz control to off and change cruz control light to red

## Turning on: system turn on (Functional)
when the speed is more than 65 km/s and mode of cruz control is off and driver hold set button for at least 3 seconds , change cruz_control_mode to working on and change cruz control light to green

## Turning off the system: cruz control turn off (Functional)
when the cruz control is on and cruz control light is green and driver hold the off button for 3 seconds , turn cruz control system off and change cruz_control_light to red

## changing mode: mode become changing speed (Functional)
When cruz control is on and cruz control light is green and driver hold acc button for 3 seconds , change mode of cruz control to change_speed_mode and make cruz control light blinking

### increasing desired speed: changing desired speed (Functional)
when mode of cruz control is change_speed_mode and driver push acc button, increase desired speed by one unit

### decreasing desired speed: changing desired speed (Functional)
when mode of cruz control is change_speed_mode and driver push dec button, decrease desired speed by one unit

### setting the speed: setting desired speed (Functional)
When mode of cruz control is change_speed_mode and driver hold set button for 5 seconds , stablize cruz control light and change mode of cruz control to working

## checking system: check (Functional)
When the cruz control light is green and mode of cruz control is off , change mode of cruz control to working

## Accuracy: Speed accuracy (Informational)
The actual speed of the car after 15 second +/- 20% have to be same as desired speed that driver set before
